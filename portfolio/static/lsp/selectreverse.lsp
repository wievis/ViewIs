(defun c:selectreverse (/ inv_ss all_ss result_ss i ent)
  (setq inv_ss (ssget "_I"))
  (setq all_ss (ssget "_X" (list (cons 410 (getvar "CTAB")) '(-4 . "<NOT") '(60 . 1) '(-4 . "NOT>"))))
  (if all_ss
    (progn
      (setq result_ss (ssadd))
      (setq i 0)
      (repeat (sslength all_ss)
        (setq ent (ssname all_ss i))
        (if (or (null inv_ss) (not (ssmemb ent inv_ss)))
          (ssadd ent result_ss)
        )
        (setq i (1+ i))
      )
      (sssetfirst nil result_ss)
    )
  )
  (princ)
)
